# Specification: Specification Document
- Description: LiftSpec

## R1 (Headline Type)
Lift Specification

### REQ-1 (Requirement Type)
A lift system is to be installed in a building
- Category: Env cond

#### REQ-30 (Requirement Type)
The building has M floors
- Category: Env cond

#### REQ-31 (Requirement Type)
The system has N lifts
- Category: Env cond

### R3 (Hierarchy Type)
Lift buttons

#### REQ-8 (Requirement Type)
Each lift has a set of buttons, one for each floor
- Category: Env cond

#### REQ-9 (Requirement Type)
Buttons illuminate when pressed
- Category: Function

#### REQ-32 (Requirement Type)
Pressing a button causes the lift to visit the corresponding floor
- Category: Function

#### REQ-10 (Requirement Type)
The illumination is cancelled when the corresponding floor is visited
- Category: Function

### R4 (Hierarchy Type)
Floor buttons

#### REQ-11 (Requirement Type)
Each floor has two buttons one to request an up-lift and one to request  down lift.
- Category: Env cond

#### REQ-12 (Requirement Type)
Top and ground floors have one button for down-lift respectively for up-lift.
- Category: Env cond

#### REQ-13 (Requirement Type)
They illuminate when pressed
- Category: Function

#### R15 (Hierarchy Type)
Cancel command condition

##### REQ-15 (Requirement Type)
When the lift arrives at the floor the command is cancelled
- Category: Function

##### REQ-16 (Requirement Type)
When the lift travels in the requested direction and stops at the floor the command is canceled
- Category: Function

### R5 (Hierarchy Type)
Commands fairness

#### REQ-19 (Requirement Type)
The algorithm used to decide which command should service has to minimize the waiting time
- Category: Function

#### REQ-20 (Requirement Type)
All requests must  be serviced eventually
- Category: Function

### R7 (Hierarchy Type)
Emergency button

#### REQ-21 (Requirement Type)
The emergency button causes a warning to be sent to the site manager
- Category: Function

##### REQ-22 (Requirement Type)
The lift is deemed 'out-of-service' after the button is pressed
- Category: Function

#### REQ-23 (Requirement Type)
Each lift has a mechanism to cancel the 'out-of-service' status
- Category: Function

### REQ-7 (Requirement Type)
When a lift has no requests to serivce it should remain at its final destination with the doors closed
- Category: Function

### REQ-5 (Requirement Type)
All requests are serviced sequencially in the directon of travel
- Category: Function

## REQ-17 (Requirement Type)

## REQ-18 (Requirement Type)
