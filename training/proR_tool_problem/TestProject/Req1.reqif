# First document

# Specification: Specification Document
- Description: Spec module A

## R1 (Headline Type)
A ProR Tutorial
- links to -> INF-2
- links to -> REQ-14

### REQ-1 (Requirement Type)
SPEC
Long text for testing the display of the html format.
- Headt: headline type used here

#### REQ-1a (Requirement Type)
First indented requirement
- Relation Type -> REQ2

#### REQ2 (Requirement Type)
Req linked to 2 other links

#### REQ4 (Requirement Type)
Multiple Reference

## INF-2 (Requirement Type)
A new Hirearchy
- Owner: Tu

### REQ-13 (Requirement Type)
objectmultiple
- Owner: ad
- Relation Type -> REQ-12
- links to -> REQ-15

#### REQ3B (Requirement Type)
Requirement within hierarchy
- Relation Type -> REQ-12

### REQ5 (Requirement Type)
Linked Relation & hierachy sibling

### REQ-15 (Requirement Type)
SameReference
- Relation Type -> REQ-13

# Specification
- Description: Spec module B

## R10 (Headline Type)
Headline1

### REQ-12 (Requirement Type)
First spec b module

### REQ-14 (Requirement Type)
SameObject
- Relation Type -> REQ-13
